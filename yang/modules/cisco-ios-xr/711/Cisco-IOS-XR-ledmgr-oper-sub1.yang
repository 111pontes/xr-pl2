submodule Cisco-IOS-XR-ledmgr-oper-sub1 {
  belongs-to Cisco-IOS-XR-ledmgr-oper {
    prefix Cisco-IOS-XR-ledmgr-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ledmgr package operational data.
     
     Copyright (c) 2013-2019 by Cisco Systems, Inc.
     All rights reserved.";

  revision 2019-10-15 {
    description
      "IOS XR 7.0.12 revision.";
    semver:module-version "2.0.0";
  }
  revision 2019-04-05 {
    description
      "Establish semantic version baseline.";
  }
  revision 2015-11-09 {
    description
      "IOS XR 6.0 revision.";
  }

  grouping LED-ATTRIBUTES {
    description
      "led attributes info bag";
    leaf led-name {
      type string;
      description
        "name of led";
    }
    leaf led-mode {
      type string;
      description
        "mode of led";
    }
    leaf led-color {
      type string;
      description
        "color of led";
    }
  }
}
