module Cisco-IOS-XR-perf-meas-oper {
  namespace "http://cisco.com/ns/yang/Cisco-IOS-XR-perf-meas-oper";
  prefix perf-meas-oper;

  import Cisco-IOS-XR-types {
    prefix xr;
  }
  import cisco-semver {
    prefix semver;
  }
  include Cisco-IOS-XR-perf-meas-oper-sub2 {
    revision-date 2019-10-19;
  }
  include Cisco-IOS-XR-perf-meas-oper-sub1 {
    revision-date 2019-10-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR perf-meas package operational data.
     
     This module contains definitions
     for the following management objects:
       performance-measurement: Performance Measurement operational
         data
       performance-measurement-responder: Performance Measurement
         operational data
     
     Copyright (c) 2013-2019 by Cisco Systems, Inc.
     All rights reserved.";

  revision 2019-10-19 {
    description
      "Added burst-interval-effective to oper data.";
    semver:module-version "2.0.0";
  }
  revision 2019-04-05 {
    description
      "Establish semantic version baseline.";
  }
  revision 2018-12-13 {
    description
      "Revision IOS XR 7.0.1 Added delay measurment for SR Policy and RSVP-TE LSP.";
  }
  revision 2017-10-17 {
    description
      "Revision Zero.";
  }
  revision 2015-11-09 {
    description
      "IOS XR 6.0 revision.";
  }

  container performance-measurement {
    config false;
    description
      "Performance Measurement operational data";
    container nodes {
      description
        "Node table for node-specific operational data";
      list node {
        key "node";
        description
          "Node-specific data for a particular node";
        container sr-policies {
          description
            "SR Policies";
          container sr-policy-details {
            description
              "Table of SR Policies detail info";
            list sr-policy-detail {
              key "policy-name";
              description
                "SR Policy information";
              leaf policy-name {
                type xr:Cisco-ios-xr-string;
                description
                  "Policy name";
              }
              uses PM-SRPOLICY-BAG;
            }
          }
          container sr-policy-delay {
            description
              "SR Policy Delay-measurement intformation";
            container sr-policy-last-advertisements {
              description
                "Table of last advertisement metrics";
              list sr-policy-last-advertisement {
                key "sr-policy-name";
                description
                  "Last advertisement metrics information";
                leaf sr-policy-name {
                  type xr:Cisco-ios-xr-string;
                  description
                    "SR Policy name";
                }
                uses PM-SRPOLICY-METRICS-BAG;
              }
            }
            container sr-policy-advertisement-histories {
              description
                "Table of advertisement histories";
              list sr-policy-advertisement-history {
                key "sr-policy-name";
                description
                  "Advertisement history information";
                leaf sr-policy-name {
                  type xr:Cisco-ios-xr-string;
                  description
                    "SR Policy name";
                }
                uses PM-SRPOLICY-HISTORY-BAG;
              }
            }
            container sr-policy-last-probe-verboses {
              description
                "Table of last probe metrics verbose";
              list sr-policy-last-probe-verbose {
                key "sr-policy-name";
                description
                  "Last probe verbose information";
                leaf sr-policy-name {
                  type xr:Cisco-ios-xr-string;
                  description
                    "SR Policy name";
                }
                uses PM-SRPOLICY-METRICS-BAG;
              }
            }
            container sr-policy-last-advertisement-verboses {
              description
                "Table of last advertisement verbose
                 information";
              list sr-policy-last-advertisement-verbose {
                key "sr-policy-name";
                description
                  "Last advertisement verbose metrics
                   information";
                leaf sr-policy-name {
                  type xr:Cisco-ios-xr-string;
                  description
                    "SR Policy name";
                }
                uses PM-SRPOLICY-METRICS-BAG;
              }
            }
            container sr-policy-last-probes {
              description
                "Table of last probe metrics";
              list sr-policy-last-probe {
                key "sr-policy-name";
                description
                  "Last probe information";
                leaf sr-policy-name {
                  type xr:Cisco-ios-xr-string;
                  description
                    "SR Policy name";
                }
                uses PM-SRPOLICY-METRICS-BAG;
              }
            }
            container sr-policy-last-aggregation-verboses {
              description
                "Table of last probe aggregation verbose";
              list sr-policy-last-aggregation-verbose {
                key "sr-policy-name";
                description
                  "Last probe aggregation verbose information";
                leaf sr-policy-name {
                  type xr:Cisco-ios-xr-string;
                  description
                    "SR Policy name";
                }
                uses PM-SRPOLICY-METRICS-BAG;
              }
            }
            container sr-policy-aggregated-histories {
              description
                "Table of aggregated probe histories";
              list sr-policy-aggregated-history {
                key "sr-policy-name";
                description
                  "Aggregated probe history information";
                leaf sr-policy-name {
                  type xr:Cisco-ios-xr-string;
                  description
                    "SR Policy name";
                }
                uses PM-SRPOLICY-HISTORY-BAG;
              }
            }
            container sr-policy-probe-histories {
              description
                "Table of probe histories";
              list sr-policy-probe-history {
                key "sr-policy-name";
                description
                  "Probe history information";
                leaf sr-policy-name {
                  type xr:Cisco-ios-xr-string;
                  description
                    "SR Policy name";
                }
                uses PM-SRPOLICY-HISTORY-BAG;
              }
            }
            container sr-policy-last-aggregations {
              description
                "Table of last aggregation";
              list sr-policy-last-aggregation {
                key "sr-policy-name";
                description
                  "Last aggregation information";
                leaf sr-policy-name {
                  type xr:Cisco-ios-xr-string;
                  description
                    "SR Policy name";
                }
                uses PM-SRPOLICY-METRICS-BAG;
              }
            }
          }
          container sr-policy-counters {
            description
              "Table of SR Policies counters info";
            list sr-policy-counter {
              key "policy-name";
              description
                "SR Policy counter information";
              leaf policy-name {
                type xr:Cisco-ios-xr-string;
                description
                  "Policy name";
              }
              uses PM-SRPOLICY-COUNTERS-BAG;
            }
          }
        }
        container rsvpte-tunnels {
          description
            "RSVP-TE tunnels";
          container rsvpte-counters {
            description
              "Table of RSVP-TE tunnel counters info";
            list rsvpte-counter {
              key "tunnel-name";
              description
                "RSVP-TE counter information";
              leaf tunnel-name {
                type xr:Interface-name;
                description
                  "Tunnel name";
              }
              uses PM-RSVPTE-COUNTERS-BAG;
            }
          }
          container rsvpte-details {
            description
              "Table of RSVP-TE tunnels detail info";
            list rsvpte-detail {
              key "tunnel-name";
              description
                "RSVP-TE information";
              leaf tunnel-name {
                type xr:Interface-name;
                description
                  "Tunnel name";
              }
              uses PM-RSVPTE-BAG;
            }
          }
          container rsvpte-delay {
            description
              "RSVP-TE tunnel delay-measurement intformation";
            container rsvpte-aggregated-histories {
              description
                "Table of aggregated probe histories";
              list rsvpte-aggregated-history {
                key "tunnel-name";
                description
                  "Aggregated probe history information";
                leaf tunnel-name {
                  type xr:Interface-name;
                  description
                    "Tunnel name";
                }
                uses PM-RSVPTE-HISTORY-BAG;
              }
            }
            container rsvpte-last-advertisements {
              description
                "Table of last advertisement metrics";
              list rsvpte-last-advertisement {
                key "tunnel-name";
                description
                  "Last advertisement metrics information";
                leaf tunnel-name {
                  type xr:Interface-name;
                  description
                    "Tunnel name";
                }
                uses PM-RSVPTE-DELAY-METRICS-BAG;
              }
            }
            container rsvpte-last-aggregations {
              description
                "Table of last probe aggregation";
              list rsvpte-last-aggregation {
                key "tunnel-name";
                description
                  "Last probe aggregation information";
                leaf tunnel-name {
                  type xr:Interface-name;
                  description
                    "SR Policy name";
                }
                uses PM-RSVPTE-DELAY-METRICS-BAG;
              }
            }
            container rsvpte-last-probes {
              description
                "Table of last probe metrics";
              list rsvpte-last-probe {
                key "tunnel-name";
                description
                  "Last probe information";
                leaf tunnel-name {
                  type xr:Interface-name;
                  description
                    "Tunnel name";
                }
                uses PM-RSVPTE-DELAY-METRICS-BAG;
              }
            }
            container rsvpte-probe-histories {
              description
                "Table of probe histories";
              list rsvpte-probe-history {
                key "tunnel-name";
                description
                  "Probe history information";
                leaf tunnel-name {
                  type xr:Interface-name;
                  description
                    "Tunnel name";
                }
                uses PM-RSVPTE-HISTORY-BAG;
              }
            }
            container rsvpte-advertisement-histories {
              description
                "Table of advertisement histories for the
                 RSVP-TE LSP";
              list rsvpte-advertisement-history {
                key "tunnel-name";
                description
                  "Advertisement history information for the
                   RSVP-TE LSP";
                leaf tunnel-name {
                  type xr:Interface-name;
                  description
                    "Tunnel name";
                }
                uses PM-RSVPTE-HISTORY-BAG;
              }
            }
          }
        }
        container summary {
          description
            "Summary information for all the measurement
             and transportation type on querier";
          uses PM-SUMMARY-BAG;
        }
        container interfaces {
          description
            "Physical and bundle interfaces";
          container interface-details {
            description
              "Interface detailed table";
            list interface-detail {
              key "interface-name";
              description
                "Detailed interface information";
              leaf interface-name {
                type xr:Interface-name;
                description
                  "Interface name";
              }
              uses PM-INTF-BAG;
            }
          }
          container interface-delay {
            description
              "Delay-measurement intformation";
            container interface-advertisement-histories {
              description
                "Table of advertisement history information";
              list interface-advertisement-history {
                key "interface-name";
                description
                  "Advertisement history information";
                leaf interface-name {
                  type xr:Interface-name;
                  description
                    "Interface name";
                }
                uses PM-INTF-HISTORY-BAG;
              }
            }
            container interface-last-aggregations {
              description
                "Table of last aggregation";
              list interface-last-aggregation {
                key "interface-name";
                description
                  "Last aggregation information";
                leaf interface-name {
                  type xr:Interface-name;
                  description
                    "Interface name";
                }
                uses PM-INTF-LAST-AGGR-BAG;
              }
            }
            container interface-probe-histories {
              description
                "Table of probe histories";
              list interface-probe-history {
                key "interface-name";
                description
                  "Probe history information";
                leaf interface-name {
                  type xr:Interface-name;
                  description
                    "Interface name";
                }
                uses PM-INTF-HISTORY-BAG;
              }
            }
            container interface-aggregated-histories {
              description
                "Table of aggregated probe histories";
              list interface-aggregated-history {
                key "interface-name";
                description
                  "Aggregated probe history information";
                leaf interface-name {
                  type xr:Interface-name;
                  description
                    "Interface name";
                }
                uses PM-INTF-HISTORY-BAG;
              }
            }
            container interface-last-probes {
              description
                "Table of last probes";
              list interface-last-probe {
                key "interface-name";
                description
                  "Last measurement information";
                leaf interface-name {
                  type xr:Interface-name;
                  description
                    "Interface name";
                }
                uses PM-INTF-LAST-PROBE-BAG;
              }
            }
            container interface-last-advertisements {
              description
                "Table of last advertisements";
              list interface-last-advertisement {
                key "interface-name";
                description
                  "Last advertisement information";
                leaf interface-name {
                  type xr:Interface-name;
                  description
                    "Interface name";
                }
                uses PM-INTF-LAST-ADVERT-BAG;
              }
            }
          }
        }
        container profile {
          description
            "Profile information for all the measurement
             and transportation type on querier";
          uses PM-PROFILE-BAG;
        }
        container distribution-records {
          description
            "Table of linecard session distribution records";
          list distribution-record {
            key "record-name";
            description
              "linecard session distribution record";
            leaf record-name {
              type xr:Cisco-ios-xr-string;
              description
                "Distribution record name";
            }
            uses PM-DR-INFO;
          }
        }
        leaf node {
          type xr:Node-id;
          description
            "Node";
        }
      }
    }
  }
  container performance-measurement-responder {
    config false;
    description
      "Performance Measurement operational data";
    container nodes {
      description
        "Node table for node-specific operational data";
      list node {
        key "node";
        description
          "Node-specific data for a particular node";
        container summary {
          description
            "Summary information for all the measurement
             and transportation type on responder";
          uses PM-RESP-SUMMARY-BAG;
        }
        container interfaces {
          description
            "Table of interfaces";
          list interface {
            key "interface-name";
            description
              "Interface information";
            leaf interface-name {
              type xr:Interface-name;
              description
                "Interface name";
            }
            uses PM-RESP-INTF-BAG;
          }
        }
        leaf node {
          type xr:Node-id;
          description
            "Node";
        }
      }
    }
  }
}
