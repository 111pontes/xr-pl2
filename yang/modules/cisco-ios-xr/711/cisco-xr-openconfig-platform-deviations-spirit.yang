module cisco-xr-openconfig-platform-deviations {
  namespace "http://cisco.com/ns/yang/cisco-xr-openconfig-platform-deviations";
  prefix oc-platformdevs;

  import openconfig-platform {
    prefix oc-platform;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for
     
     openconfig-platform.yang@2018-06-03
     
     on Cisco IOS-XR devices.
     
     Copyright (c) 2017-2019 by Cisco Systems, Inc.
     All rights reserved.";

  revision 2018-12-05 {
    description
      "Initial revision applicable to IOS-XR 6.6.1";
  }

  deviation "/oc-platform:components/oc-platform:component/oc-platform:state/oc-platform:mfg-date" {
    deviate not-supported;
  }
  deviation "/oc-platform:components/oc-platform:component/oc-platform:properties/oc-platform:property" {
    deviate not-supported;
  }
}
