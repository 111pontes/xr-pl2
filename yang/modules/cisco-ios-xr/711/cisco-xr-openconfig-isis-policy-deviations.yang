module cisco-xr-openconfig-isis-policy-deviations {
  namespace "http://cisco.com/ns/yang/cisco-xr-openconfig-isis-policy-deviations";
  prefix cisco-xr-oc-isis-pol-devs;

  import openconfig-routing-policy {
    prefix rpol;
  }
  import openconfig-isis-policy {
    prefix isis-pol;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains the deviations of Open Config ISIS Policy YANG
     set for Cisco IOS-XR.
     
     Copyright (c) 2019 by Cisco Systems, Inc.
     All rights reserved.";

  revision 2019-06-10 {
    description
      "Updated revision applicable to IOS-XR 7.1.1";
  }

  deviation "/rpol:routing-policy/rpol:policy-definitions/rpol:policy-definition/rpol:statements/rpol:statement/rpol:conditions/isis-pol:isis-conditions/isis-pol:config/isis-pol:level-eq" {
    deviate not-supported;
  }
  deviation "/rpol:routing-policy/rpol:policy-definitions/rpol:policy-definition/rpol:statements/rpol:statement/rpol:conditions/isis-pol:isis-conditions/isis-pol:state/isis-pol:level-eq" {
    deviate not-supported;
  }
  deviation "/rpol:routing-policy/rpol:policy-definitions/rpol:policy-definition/rpol:statements/rpol:statement/rpol:actions/isis-pol:isis-actions/isis-pol:config/isis-pol:set-level" {
    deviate not-supported;
  }
  deviation "/rpol:routing-policy/rpol:policy-definitions/rpol:policy-definition/rpol:statements/rpol:statement/rpol:actions/isis-pol:isis-actions/isis-pol:state/isis-pol:set-level" {
    deviate not-supported;
  }
  deviation "/rpol:routing-policy/rpol:policy-definitions/rpol:policy-definition/rpol:statements/rpol:statement/rpol:actions/isis-pol:isis-actions/isis-pol:config/isis-pol:set-metric-type" {
    deviate not-supported;
  }
  deviation "/rpol:routing-policy/rpol:policy-definitions/rpol:policy-definition/rpol:statements/rpol:statement/rpol:actions/isis-pol:isis-actions/isis-pol:state/isis-pol:set-metric-type" {
    deviate not-supported;
  }
  deviation "/rpol:routing-policy/rpol:policy-definitions/rpol:policy-definition/rpol:statements/rpol:statement/rpol:actions/isis-pol:isis-actions/isis-pol:config/isis-pol:set-metric" {
    deviate not-supported;
  }
  deviation "/rpol:routing-policy/rpol:policy-definitions/rpol:policy-definition/rpol:statements/rpol:statement/rpol:actions/isis-pol:isis-actions/isis-pol:state/isis-pol:set-metric" {
    deviate not-supported;
  }
}
