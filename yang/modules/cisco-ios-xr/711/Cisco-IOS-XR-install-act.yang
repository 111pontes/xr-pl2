module Cisco-IOS-XR-install-act {
  namespace "http://cisco.com/ns/yang/Cisco-IOS-XR-install-act";
  prefix install-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install actions.
     
     Copyright (c) 2018-2019 by Cisco Systems, Inc.
     All rights reserved.";

  revision 2019-10-01 {
    description
      "Made changes to be RFC6087 compliant";
    semver:module-version "1.0.1";
  }
  revision 2019-04-05 {
    description
      "Establish semantic version baseline.";
  }
  revision 2018-10-05 {
    description
      "IOS XR 7.0.1 revision.";
  }

  typedef replace-source-type {
    type enumeration {
      enum "local" {
        description
          "Install from a local file path";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
    }
    description
      "replace source type";
  }

  typedef packages-source-type {
    type enumeration {
      enum "local" {
        description
          "Install from a local file path or repository";
      }
      enum "http" {
        description
          "Install over http";
      }
      enum "https" {
        description
          "Install over https";
      }
      enum "scp" {
        description
          "Install over scp";
      }
      enum "ftp" {
        description
          "Install over ftp";
      }
      enum "tftp" {
        description
          "Install over tftp";
      }
      enum "sftp" {
        description
          "Install over sftp";
      }
      enum "any-configured-repository" {
        description
          "Install from any configured repository";
      }
      enum "configured-repository" {
        description
          "Install from the given repository";
      }
    }
    description
      "packages source type";
  }

  typedef config-type {
    type enumeration {
      enum "ignore" {
        description
          "Ignore the configuration in the given ISO";
      }
      enum "merge" {
        description
          "Merge the configuration in the given ISO with existing
           configuration";
      }
      enum "replace" {
        description
          "Replace the existing configuration with the configuration
           in the given ISO";
      }
    }
    description
      "config type";
  }

  rpc install-replace {
    description
      "Replace the existing software with that from the given ISO";
    input {
      leaf source-type {
        type replace-source-type;
        default "local";
        description
          "Type of source used to obtain the ISO";
      }
      leaf source {
        type string;
        mandatory true;
        description
          "Path to the location of the ISO";
      }
      leaf file {
        type string;
        mandatory true;
        description
          "Name of the ISO to install";
      }
      leaf commit {
        type boolean;
        default "false";
        description
          "Commit at the end of the replace operation, if the
           software is successfully applied";
      }
      leaf config {
        type config-type;
        default "ignore";
        description
          "Action to take on any configuration present in the ISO";
      }
    }
    csc:xr-task "pkg-mgmt";
  }
  rpc install {
    description
      "Install packages from a given source";
    input {
      container packages {
        description
          "Set of packages to install.  Leave empty if 'update-all'
           is True";
        leaf-list packagename {
          type string;
          description
            "package name";
        }
      }
      leaf update-all {
        type boolean;
        default "false";
        description
          "True to update all packages using the given source, False
           to only install or update the specified packages";
      }
      leaf source-type {
        type packages-source-type;
        default "local";
        description
          "Type of source used to obtain the packages";
      }
      leaf source {
        type string;
        description
          "Path to the location of the packages.  If source-type is
           'any-configured-repository' this field is unused, and if
           source-type is 'configured-repository' this should be the
           name of the repository to use.";
      }
    }
    csc:xr-task "pkg-mgmt";
  }
  rpc install-commit {
    description
      "Commit the current software, such that it will persist over reload.";
    csc:xr-task "pkg-mgmt";
  }
}
