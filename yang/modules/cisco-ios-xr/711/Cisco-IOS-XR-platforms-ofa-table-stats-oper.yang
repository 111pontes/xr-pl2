module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2019-06-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: Stats Data
     
     Copyright (c) 2013-2019 by Cisco Systems, Inc.
     All rights reserved.";

  revision 2019-06-14 {
    description
      "Added the Yang Model for ofa sw resources";
  }
  revision 2019-04-05 {
    description
      "Establish semantic version baseline.";
  }
  revision 2015-11-09 {
    description
      "IOS XR 6.0 revision.";
  }

  typedef Max-re-source-s-table {
    type uint32 {
      range "0..247";
    }
    description
      "Max re source s table";
  }

  container ofa {
    config false;
    description
      "Stats Data";
    container stats {
      description
        "Stats";
      container nodes {
        description
          "OFA data for available nodes";
        list node {
          key "node-name";
          description
            "OFA operational data for a particular node";
          container table-datas {
            description
              "OFA Resources table";
            list table-data {
              key "resource";
              description
                "Resources table";
              leaf resource {
                type Max-re-source-s-table;
                description
                  "Resource type";
              }
              uses OFA-NPD-SYSDB-TABLE-RESOURCE;
            }
          }
          leaf node-name {
            type xr:Node-id;
            description
              "Node ID";
          }
        }
      }
    }
  }
}
