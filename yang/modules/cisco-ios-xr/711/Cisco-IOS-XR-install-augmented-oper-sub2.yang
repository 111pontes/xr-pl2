submodule Cisco-IOS-XR-install-augmented-oper-sub2 {
  belongs-to Cisco-IOS-XR-install-augmented-oper {
    prefix Cisco-IOS-XR-install-augmented-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR install-augmented package operational data.
     
     Copyright (c) 2013-2019 by Cisco Systems, Inc.
     All rights reserved.";

  revision 2019-04-05 {
    description
      "Establish semantic version baseline.";
    semver:module-version "1.1.0";
  }
  revision 2015-11-09 {
    description
      "IOS XR 6.0 revision.";
  }

  typedef Inst-activation {
    type enumeration {
      enum "restart" {
        value 0;
        description
          "Process restart";
      }
      enum "reload" {
        value 1;
        description
          "Reload";
      }
      enum "least-impactful" {
        value 2;
        description
          "Least impactful";
      }
    }
    description
      "Activation type";
  }

  typedef Inst-package-abort {
    type enumeration {
      enum "latest" {
        value 0;
        description
          "Latest packaging operation";
      }
      enum "all-since-apply" {
        value 1;
        description
          "All packaging operations since the last apply";
      }
    }
    description
      "Package abort type";
  }

  typedef String1 {
    type string;
    description
      "String1";
  }
}
