module Cisco-IOS-XR-cofo-csi-ma-oper {
  namespace "http://cisco.com/ns/yang/Cisco-IOS-XR-cofo-csi-ma-oper";
  prefix cofo-csi-ma-oper;

  import Cisco-IOS-XR-types {
    prefix xr;
  }
  import cisco-semver {
    prefix semver;
  }
  include Cisco-IOS-XR-cofo-csi-ma-oper-sub1 {
    revision-date 2019-06-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cofo-csi-ma package operational data.
     
     This module contains definitions
     for the following management objects:
       csima: Csi-ma operational data
     
     Copyright (c) 2013-2019 by Cisco Systems, Inc.
     All rights reserved.";

  revision 2019-06-16 {
    description
      "Enhancement to support configuration of CSI-Ether MTU";
    semver:module-version "1.1.0";
  }
  revision 2019-04-05 {
    description
      "Establish semantic version baseline.";
  }
  revision 2015-11-09 {
    description
      "IOS XR 6.0 revision.";
  }

  container csima {
    config false;
    description
      "Csi-ma operational data";
    container nodes {
      description
        "Node-specific operational data";
      list node {
        key "node-name";
        description
          "Operational data for a particular node";
        container rack-ids {
          description
            "Connected node slices information";
          list rack-id {
            key "rack-id";
            description
              "Connected node rack-id";
            leaf rack-id {
              type uint32 {
                range "0..65535";
              }
              description
                "Rack Id";
            }
            list slot-id {
              key "slot-id";
              description
                "NodeInfo for a NodeId";
              leaf slot-id {
                type uint32 {
                  range "0..65535";
                }
                description
                  "Slot Id";
              }
              uses CSI-MA-NODE-INFO;
            }
          }
        }
        container interface-names {
          description
            "Interface data for csi interfaces";
          list interface-name {
            key "csi-index";
            description
              "Interface data for an Interface";
            leaf csi-index {
              type uint32 {
                range "1..15";
              }
              description
                "CSI Index";
            }
            uses CSI-MA-INTERFACE-INFO;
          }
        }
        container global {
          description
            "Global data associated with csi-ma";
          uses CSI-MA-GLOBAL-INFO;
        }
        container sdr-ids {
          description
            "Remote data for SDR ID";
          list sdr-id {
            key "sdr-id";
            description
              "Remote data for sdr-id";
            leaf sdr-id {
              type uint32 {
                range "1..65535";
              }
              description
                "Sdr Id";
            }
            uses CSI-MA-REMOTE-INFO;
          }
        }
        container csi-indexes {
          description
            "Admin data for csi-index";
          list csi-index {
            key "csi-index";
            description
              "Admin data for a csi-index";
            leaf csi-index {
              type uint32 {
                range "1..15";
              }
              description
                "CSI Index";
            }
            uses CSI-MA-ADMIN-INFO;
          }
        }
        leaf node-name {
          type xr:Node-id;
          description
            "The node";
        }
      }
    }
  }
}
