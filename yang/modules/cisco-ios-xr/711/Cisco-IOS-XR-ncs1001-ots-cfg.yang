module Cisco-IOS-XR-ncs1001-ots-cfg {
  namespace "http://cisco.com/ns/yang/Cisco-IOS-XR-ncs1001-ots-cfg";
  prefix ncs1001-ots-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-ots package configuration.
     
     This module contains definitions
     for the following management objects:
       hardware-module: NCS1k HW module config
     
     Copyright (c) 2013-2019 by Cisco Systems, Inc.
     All rights reserved.";

  revision 2019-04-05 {
    description
      "Establish semantic version baseline.";
    semver:module-version "2.0.0";
  }
  revision 2018-03-20 {
    description
      "added Otdr management.";
  }
  revision 2015-11-09 {
    description
      "IOS XR 6.0 revision.";
  }

  typedef Ots-amplifier-node {
    type enumeration {
      enum "term" {
        value 0;
        description
          "Nodetype TERM";
      }
      enum "ila" {
        value 1;
        description
          "Nodetype InLine Amplifier";
      }
      enum "roadm" {
        value 2;
        description
          "Nodetype ROADM";
      }
    }
    description
      "Ots amplifier node";
  }

  typedef Ots-amplifier-grid-mode {
    type enumeration {
      enum "100g-hz" {
        value 0;
        description
          "100GHz mode";
      }
      enum "50g-hz" {
        value 1;
        description
          "50GHz mode";
      }
      enum "gr-idle-ss" {
        value 2;
        description
          "Gridless mode";
      }
    }
    description
      "Ots amplifier grid mode";
  }

  typedef Ots-otdr-scan {
    type enumeration {
      enum "auto" {
        value 0;
        description
          "Auto";
      }
    }
    description
      "Ots otdr scan";
  }

  typedef Ots-otdr-direction {
    type enumeration {
      enum "tx" {
        value 0;
        description
          "Tx";
      }
      enum "rx" {
        value 1;
        description
          "Rx";
      }
    }
    description
      "Ots otdr direction";
  }

  typedef Ots-psm-primary-path {
    type enumeration {
      enum "working" {
        value 1;
        description
          "Working port";
      }
      enum "protected" {
        value 2;
        description
          "Protected port";
      }
    }
    description
      "Ots psm primary path";
  }

  typedef Ots-psm-lockout-from {
    type enumeration {
      enum "working" {
        value 1;
        description
          "Working port";
      }
      enum "protected" {
        value 2;
        description
          "Protected port";
      }
    }
    description
      "Ots psm lockout from";
  }

  container hardware-module {
    description
      "NCS1k HW module config";
    list node {
      key "location";
      description
        "Node";
      leaf location {
        type xr:Cisco-ios-xr-string;
        description
          "Fully qualified line card specification";
      }
      list slot {
        key "slot-id";
        description
          "Slot Id";
        container otdr-auto-scans {
          description
            "Otdr Auto Scan";
          list otdr-auto-scan {
            key "port";
            description
              "Otdr Auto Scan";
            container auto-scan {
              description
                "OTDR Event Triggered Automatic Scan
                 Configuration";
              leaf otdr-ip-address {
                type inet:ip-address-no-zone;
                description
                  "IP address of OTDR module host";
              }
              leaf otdr-farend-ip-address {
                type inet:ip-address-no-zone;
                description
                  "IP address of OTDR far-end host";
              }
              leaf otdr-far-end-slot-id {
                type uint32 {
                  range "1..3";
                }
                description
                  "Set OTDR far-end Slot Number";
              }
              leaf scan-type {
                type Ots-otdr-scan;
                description
                  "Scan Type AUTO";
              }
            }
            leaf port {
              type uint32;
              description
                "Port Id";
            }
          }
        }
        container otdrs {
          description
            "OTDR Configs";
          list otdr {
            key "port direction";
            description
              "Otdr Id";
            container periodic-scan {
              description
                "Periodic Scan";
              leaf minutes {
                type uint32 {
                  range "30..600000";
                }
                units "minute";
                description
                  "Periodicity in minutes (min value supported
                   30 min)";
              }
            }
            container mode-auto {
              description
                "Mode Auto";
              leaf loss-rel-threshold {
                type uint32 {
                  range "1..300";
                }
                description
                  "relative Loss Threshold, supported values
                   [1,300] in units of 0.1dB";
              }
              leaf loss-sensitivity {
                type uint32 {
                  range "4..50";
                }
                description
                  "Otdr Loss Sensitivity, supported values [4
                   ,50] in units of 0.1dB";
              }
              leaf reflection-rel-threshold {
                type uint32 {
                  range "1..300";
                }
                description
                  "Relative Reflection Threshold, supported
                   values [1,300] in units of 0.1dB";
              }
              leaf reflection-sensitivity {
                type int32 {
                  range "-400..-140";
                }
                description
                  "Otdr Reflection Sensitivity, supported
                   values [-400,-140] in units of 0.1dB";
              }
            }
            container mode-expert {
              description
                "Mode Expert";
              leaf fiber-resolution {
                type uint32 {
                  range "0..100";
                }
                description
                  "Fiber Resolution in meters, supported
                   values [0,100]";
              }
              leaf capture-length {
                type uint32 {
                  range "1..150";
                }
                description
                  "Capture Length in Km, supported values [1
                   ,150]";
              }
              leaf loss-rel-threshold {
                type uint32 {
                  range "1..300";
                }
                description
                  "relative Loss Threshold, supported values
                   [1,300] in units of 0.1dB";
              }
              leaf pulse-width {
                type uint32 {
                  range "8..100000";
                }
                units "nanosecond";
                description
                  "Pulse Width in nanoseconds, supported
                   values [8,100000]";
              }
              leaf measure-time {
                type uint32 {
                  range "1..360";
                }
                units "second";
                description
                  "Measure time in seconds, supported values
                   [1,360]";
              }
              leaf loss-sensitivity {
                type uint32 {
                  range "4..50";
                }
                description
                  "Otdr Loss Sensitivity, supported values [4
                   ,50] in units of 0.1dB";
              }
              leaf reflection-rel-threshold {
                type uint32 {
                  range "1..300";
                }
                description
                  "Relative Reflection Threshold, supported
                   values [1,300] in units of 0.1dB";
              }
              leaf capture-offset {
                type uint32 {
                  range "0..150";
                }
                description
                  "Capture Offset in Km, supported values [0
                   ,150]";
              }
              leaf span-length {
                type uint32 {
                  range "1..150";
                }
                description
                  "Span Length in Km, supported values [1,150]";
              }
              leaf reflection-sensitivity {
                type int32 {
                  range "-400..-140";
                }
                description
                  "Otdr Reflection Sensitivity, supported
                   values [-400,-140] in units of 0.1dB";
              }
            }
            leaf total-loss {
              type uint32 {
                range "0..500";
              }
              description
                "Otdr Insertion Loss, supported values [0
                 ,500] in units of 0.1dB";
            }
            leaf port {
              type uint32 {
                range "1..2";
              }
              description
                "Port Id";
            }
            leaf direction {
              type Ots-otdr-direction;
              description
                "Direction Id";
            }
          }
        }
        container otdr-thresholds {
          description
            "Otdr Threshold";
          list otdr-threshold {
            key "port";
            description
              "Otdr Threshold";
            leaf loss-abs-threshold {
              type uint32 {
                range "1..300";
              }
              description
                "Absolute Loss Threshold, supported values [1
                 ,300] in units of 0.1dB";
            }
            leaf reflection-abs-threshold {
              type int32 {
                range "-500..0";
              }
              description
                "Absolute Reflection Threshold, supported
                 values [-500,0] in units of 0.1dB";
            }
            leaf orl-abs-threshold {
              type uint32 {
                range "140..400";
              }
              description
                "Absolute Orl Threshold, supported values
                 [140,400] in units of 0.1dB";
            }
            leaf port {
              type uint32;
              description
                "Port Id";
            }
          }
        }
        container amplifier {
          description
            "Amplifier Configs";
          container otdr-auto-scan {
            description
              "OTDR Event Triggered Automatic Scan
               Configuration";
            leaf otdr-ip-address {
              type inet:ip-address-no-zone;
              description
                "IP address of OTDR module host";
            }
            leaf otdr-slot-id {
              type uint32 {
                range "1..3";
              }
              description
                "Set OTDR Slot Number";
            }
            leaf otdr-port-id {
              type uint32 {
                range "1..2";
              }
              description
                "Set OTDR Port Number";
            }
            leaf ampli-farend-ip-address {
              type inet:ip-address-no-zone;
              description
                "IP address of amplifier far-end host";
            }
            leaf ampli-far-end-slot-id {
              type uint32 {
                range "1..3";
              }
              description
                "Set amplifier far-end Slot Number";
            }
            leaf scan-type {
              type Ots-otdr-scan;
              description
                "Scan Type AUTO";
            }
          }
          container remote-node {
            description
              "RemoteNode Configuration";
            leaf local-ip-address {
              type inet:ip-address-no-zone;
              description
                "IP address of local host";
            }
            leaf remote-ip-address {
              type inet:ip-address-no-zone;
              description
                "IP address of remote host";
            }
            leaf remote-slot-id {
              type uint32 {
                range "1..3";
              }
              description
                "Set remote Slot";
            }
          }
          container span-loss {
            description
              "SpanLoss configuration";
            leaf enable {
              type boolean;
              description
                "Span Loss enabled";
            }
            leaf delta {
              type uint32 {
                range "0..500";
              }
              description
                "Set Span Loss change delta value";
            }
          }
          container channel-widths {
            description
              "Amplifier Channel Width Configs";
            list channel-width {
              key "channel-id";
              description
                "Channel Identifier";
              leaf channel-width {
                type uint32 {
                  range "1000..8000";
                }
                description
                  "Set Channel Width in uints of 0.1GHz,
                   allowed values in step of 250";
              }
              leaf channel-id {
                type uint32 {
                  range "1..96";
                }
                description
                  "Channel Identifier";
              }
            }
          }
          leaf flex-mode {
            type boolean;
            description
              "FlexMode configuration";
          }
          leaf node-type {
            type Ots-amplifier-node;
            description
              "Define the type of node in which the
               amplifier is set to work";
          }
          leaf auto-threshold {
            type boolean;
            description
              "Amplifier automatic rx-low threshold set
               enabled";
          }
          leaf grid-mode {
            type Ots-amplifier-grid-mode;
            description
              "Define the working mode for the optical
               module";
          }
          leaf udc-vlan {
            type uint32 {
              range "2..4080";
            }
            description
              "Define the VLAN ID in range <2-4080>";
          }
        }
        container psm {
          description
            "PSM Configs";
          container auto-threshold {
            description
              "Psm Automatic Threshold Setting";
            leaf enable {
              type boolean;
              description
                "PSM revertive enabled";
            }
            leaf delta {
              type uint32 {
                range "0..800";
              }
              description
                "Set auto threshold delta";
            }
          }
          container relative-switch-threshold {
            description
              "Psm Relative Switch Threshold";
            leaf psm-relative-switch-threshold {
              type uint32 {
                range "0..800";
              }
              description
                "Set Psm Relative Switch Threshold";
            }
            leaf psm-relative-switch-threshold-offset {
              type int32 {
                range "-300..300";
              }
              description
                "Set Psm Relative Switch Threshold Offset";
            }
          }
          container revertive {
            description
              "PSM Revertive Configuration";
            leaf enable {
              type boolean;
              description
                "PSM revertive enabled";
            }
            leaf wtr {
              type uint32 {
                range "0..4294967295";
              }
              units "second";
              description
                "Set wait time to restore in seconds";
            }
          }
          leaf mono-dir {
            type boolean;
            description
              "Psm Uni directional configuration";
          }
          leaf primary-path {
            type Ots-psm-primary-path;
            description
              "Select Psm Primary Path";
          }
          leaf path-protection {
            type boolean;
            description
              "Psm path protection configuration";
          }
          leaf section-protection {
            type boolean;
            description
              "Psm section protection configuration";
          }
          leaf lockout-from {
            type Ots-psm-lockout-from;
            description
              "Exclude selected port from protection";
          }
        }
        leaf slot-id {
          type uint32 {
            range "1..3";
          }
          description
            "Set Slot";
        }
      }
    }
  }
}
