submodule Cisco-IOS-XR-NCS-BDplatforms-npu-resources-oper-sub1 {
  belongs-to Cisco-IOS-XR-NCS-BDplatforms-npu-resources-oper {
    prefix Cisco-IOS-XR-NCS-BDplatforms-npu-resources-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR NCS-BDplatforms-npu-resources package operational data.
     
     Copyright (c) 2013-2019 by Cisco Systems, Inc.
     All rights reserved.";

  revision 2019-04-05 {
    description
      "Establish semantic version baseline.";
    semver:module-version "1.1.0";
  }
  revision 2015-11-09 {
    description
      "IOS XR 6.0 revision.";
  }

  grouping OFA-SYSDB-LT-HW-RESOURCE {
    description
      "Logical table accounting for that bank";
    leaf lt-id {
      type uint32;
      description
        "lt id";
    }
    leaf name {
      type string;
      description
        "name";
    }
    leaf hw-entries {
      type uint32;
      description
        "hw entries";
    }
    leaf sw-entries {
      type uint32;
      description
        "sw entries";
    }
  }

  grouping OFA-SYSDB-NPU-RESOURCE-OOR-ST {
    description
      "OOR info for that bank";
    leaf is-oor-valid {
      type boolean;
      description
        "Is this OOR struct valid";
    }
    leaf red-oor-threshold {
      type uint32;
      description
        "OOR red threshold in terms of entries";
    }
    leaf yellow-oor-threshold {
      type uint32;
      description
        "OOR yellow threshold in terms of entries";
    }
    leaf oor-change-count {
      type uint32;
      description
        "Counts number of OOR transitions";
    }
    leaf oor-state-change-time1 {
      type string {
        length "0..16";
      }
      description
        "OOR state change time 1";
    }
    leaf oor-state-change-time2 {
      type string {
        length "0..16";
      }
      description
        "OOR state change time 2";
    }
    leaf oor-state {
      type string {
        length "0..16";
      }
      description
        "OOR state string";
    }
  }

  grouping OFA-SYSDB-NPU-RESOURCE-COUNTER-ST {
    description
      "Counter information for that bank";
    leaf is-counter-valid {
      type boolean;
      description
        "Is this counter struct valid";
    }
    leaf is-max-valid {
      type boolean;
      description
        "Is Max valid";
    }
    leaf max-entries {
      type uint32;
      description
        "Maximum entries in hardware";
    }
    leaf inuse-entries {
      type uint32;
      description
        "In use entries for this bank from hardware";
    }
  }

  grouping OFA-SYSDB-NPU-HW-BANK-RESOURCE {
    description
      "Per bank resource info";
    container counter {
      description
        "Counter values for this bank";
      uses OFA-SYSDB-NPU-RESOURCE-COUNTER-ST;
    }
    container oor-state {
      description
        "OOR state for this bank";
      uses OFA-SYSDB-NPU-RESOURCE-OOR-ST;
    }
    leaf is-bank-valid {
      type boolean;
      description
        "is this bank valid/skip";
    }
    leaf bank-id {
      type uint32;
      description
        "Hierarchical bank id";
    }
    leaf bank-name {
      type string {
        length "0..64";
      }
      description
        "Hierarchical bank name generated in TIDL";
    }
    leaf bank-info {
      type string {
        length "0..64";
      }
      description
        "Custom bank info";
    }
    leaf is-bank-info-valid {
      type boolean;
      description
        "Is Bank info valid";
    }
    leaf num-lt {
      type uint32;
      description
        "Number of logical table array elements";
    }
    list lt-hwr {
      description
        "Logical OFA tables for npu resource bank";
      uses OFA-SYSDB-LT-HW-RESOURCE;
    }
  }

  grouping OFA-SYSDB-NPU-HW-RESOURCE {
    description
      "Per NPU structure for a hw resource";
    leaf npu-id {
      type uint32;
      description
        "npu id";
    }
    leaf red-oor-threshold-percent {
      type uint32;
      description
        "red oor threshold percent";
    }
    leaf yellow-oor-threshold-percent {
      type uint32;
      description
        "yellow oor threshold percent";
    }
    leaf num-bank {
      type int32;
      description
        "Bank count for hierarchical NPU resource";
    }
    list bank {
      description
        "List of Hierarchical banks for that NPU resource";
      uses OFA-SYSDB-NPU-HW-BANK-RESOURCE;
    }
  }

  grouping OFA-SYSDB-HW-RESOURCE {
    description
      "Resource level information";
    leaf resource-id {
      type uint32;
      description
        "resource id";
    }
    leaf name {
      type string;
      description
        "name";
    }
    leaf num-npus {
      type uint32;
      description
        "num npus";
    }
    leaf cmd-invalid {
      type boolean;
      description
        "cmd invalid";
    }
    leaf asic-type {
      type uint32;
      description
        "asic type";
    }
    list npu-hwr {
      description
        "npu hwr";
      uses OFA-SYSDB-NPU-HW-RESOURCE;
    }
  }

  grouping OFA-SYSDB-STATS-APP-USAGE {
    description
      "OFA SYSDB STATS APP USAGE";
    leaf app-type {
      type string;
      description
        "app type";
    }
    leaf num-cntrs-for-app {
      type uint32;
      description
        "num cntrs for app";
    }
    leaf num-cntrs-used {
      type uint32;
      description
        "num cntrs used";
    }
  }

  grouping OFA-SYSDB-STATS-CNTR-ENG {
    description
      "OFA SYSDB STATS CNTR ENG";
    leaf state {
      type string;
      description
        "state";
    }
    leaf core-id {
      type uint32;
      description
        "core id";
    }
    list apps-info {
      description
        "apps info";
      uses OFA-SYSDB-STATS-APP-USAGE;
    }
  }

  grouping OFA-SYSDB-STATS-DB-APP-USAGE {
    description
      "OFA SYSDB STATS DB APP USAGE";
    leaf app-type {
      type string;
      description
        "app type";
    }
    leaf num-cntrs-for-app {
      type uint32;
      description
        "num cntrs for app";
    }
    leaf num-cntrs-used-core0 {
      type uint32;
      description
        "num cntrs used core0";
    }
    leaf num-cntrs-used-core1 {
      type uint32;
      description
        "num cntrs used core1";
    }
  }

  grouping OFA-SYSDB-STATS-CNTR-DB {
    description
      "OFA SYSDB STATS CNTR DB";
    leaf state {
      type string;
      description
        "state";
    }
    list apps-info {
      description
        "apps info";
      uses OFA-SYSDB-STATS-DB-APP-USAGE;
    }
  }

  grouping OFA-SYSDB-STATS-HW-RESOURCE {
    description
      "OFA SYSDB STATS HW RESOURCE";
    leaf sys-type {
      type uint32;
      description
        "sys type";
    }
    leaf sys-cp-cnfg-prof {
      type uint32;
      description
        "sys cp cnfg prof";
    }
    leaf next-avail-cp-id {
      type uint32;
      description
        "next avail cp id";
    }
    leaf num-cntr-dbs {
      type uint32;
      description
        "num cntr dbs";
    }
    leaf num-cntr-engines {
      type uint32;
      description
        "num cntr engines";
    }
    list cntr-db {
      description
        "cntr db";
      uses OFA-SYSDB-STATS-CNTR-DB;
    }
    list cntr-engine {
      description
        "cntr engine";
      uses OFA-SYSDB-STATS-CNTR-ENG;
    }
  }
}
