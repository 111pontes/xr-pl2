submodule Cisco-IOS-XR-platforms-ofa-table-stats-oper-sub1 {
  belongs-to Cisco-IOS-XR-platforms-ofa-table-stats-oper {
    prefix Cisco-IOS-XR-platforms-ofa-table-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR platforms-ofa-table-stats package operational data.
     
     Copyright (c) 2013-2019 by Cisco Systems, Inc.
     All rights reserved.";

  revision 2019-06-14 {
    description
      "Added the Yang Model for ofa sw resources";
  }
  revision 2019-04-05 {
    description
      "Establish semantic version baseline.";
  }
  revision 2015-11-09 {
    description
      "IOS XR 6.0 revision.";
  }

  typedef Crud-scope {
    type enumeration {
      enum "ofa-display-per-npu-crud-counter-s" {
        value 0;
        description
          "ofa display per npu crud counter s";
      }
      enum "ofa-display-global-crud-counter-s" {
        value 1;
        description
          "ofa display global crud counter s";
      }
    }
    description
      "HW CRUD COUNTERS SCOPE";
  }

  grouping OFA-USER-DEFINED-STATS-VALUE {
    description
      "Content of user defined stats";
    leaf npu-id {
      type uint32;
      description
        "NPU ID for which stats are present";
    }
    leaf value {
      type uint64;
      description
        "Value of the stats";
    }
    leaf timestamp {
      type uint64;
      description
        "Timestamp value of the stats";
    }
  }

  grouping OFA-USER-DEFINED-STATS {
    description
      "User defined stats information";
    leaf description {
      type string {
        length "0..256";
      }
      description
        "Description to print for each user defined stats";
    }
    list user-defined-stats-value {
      description
        "Per npu content of each user defined stats";
      uses OFA-USER-DEFINED-STATS-VALUE;
    }
  }

  grouping OFA-SYSDB-GLOBAL-CRUD-STATS-ST {
    description
      "OFA SYSDB GLOBAL CRUD STATS ST";
    leaf create-hw-fail {
      type uint64;
      description
        "Number of failed create requests in the hw -
         global scope";
    }
    leaf update-hw-fail {
      type uint64;
      description
        "Number of failed update requests in the hw -
         global scope";
    }
    leaf delete-hw-fail {
      type uint64;
      description
        "Number of failed delete requests in the hw -
         global scope";
    }
  }

  grouping OFA-SYSDB-NPU-CRUD-STATS-ST {
    description
      "OFA SYSDB NPU CRUD STATS ST";
    leaf npu-id {
      type uint32;
      description
        "NPU id of the current stats instance";
    }
    leaf create-hw-fail {
      type uint32;
      description
        "Number of failed create requests in the hw - per
         NPU scope";
    }
    leaf update-hw-fail {
      type uint32;
      description
        "Number of failed update requests in the hw per
         NPU scope";
    }
    leaf delete-hw-fail {
      type uint32;
      description
        "Number of failed delete requests in the hw per
         NPU scope";
    }
  }

  grouping OFA-SYSDB-NPU-CRUD-LIST {
    description
      "OFA SYSDB NPU CRUD LIST";
    list ofa-sysdb-npu-crud {
      description
        "ofa sysdb npu crud";
      uses OFA-SYSDB-NPU-CRUD-STATS-ST;
    }
  }

  grouping UNION-HW-CRUD-COUNTER-S {
    description
      "UNION HW CRUD COUNTERS";
    container npu-crud-list {
      when "../discriminator = 'ofa-display-per-npu-crud-counter-s'" {
        description
          "../discriminator =
           'OFA_DISPLAY_PER_NPU_CRUD_COUNTERS'";
      }
      description
        "npu crud list";
      uses OFA-SYSDB-NPU-CRUD-LIST;
    }
    container global-crud-st {
      when "../discriminator = 'ofa-display-global-crud-counter-s'" {
        description
          "../discriminator =
           'OFA_DISPLAY_GLOBAL_CRUD_COUNTERS'";
      }
      description
        "global crud st";
      uses OFA-SYSDB-GLOBAL-CRUD-STATS-ST;
    }
    leaf discriminator {
      type Crud-scope;
      description
        "discriminator";
    }
  }

  grouping OFA-SYSDB-TABLE-RESOURCE {
    description
      "OFA SYSDB TABLE RESOURCE";
    container hw-crud-counters {
      description
        "Global / Per NPU HW CRUD counters";
      uses UNION-HW-CRUD-COUNTER-S;
    }
    leaf table-id {
      type uint32;
      description
        "Table id";
    }
    leaf name {
      type string {
        length "0..64";
      }
      description
        "Table name";
    }
    leaf is-global {
      type boolean;
      description
        "Is Table scope global";
    }
    leaf display-per-npu {
      type uint8;
      description
        "Is CRUD stats' display scope per NPU or global";
    }
    leaf num-npus {
      type uint32;
      description
        "Number of NPUs";
    }
    leaf table-specific-list {
      type string;
      description
        "Table specific data";
    }
    leaf create-req {
      type uint64;
      description
        "Number of create requests";
    }
    leaf delete-req {
      type uint64;
      description
        "Number of delete requests";
    }
    leaf update-req {
      type uint64;
      description
        "Number of update requests";
    }
    leaf get-req {
      type uint64;
      description
        "Number of get requests";
    }
    leaf err-ref-resolve {
      type uint32;
      description
        "OFA Error - Resolve Reference";
    }
    leaf err-db-notfound {
      type uint32;
      description
        "OFA Error - Not found in DB";
    }
    leaf err-db-exists {
      type uint32;
      description
        "OFA Error - Entry exists in DB";
    }
    leaf err-db-nomem {
      type uint32;
      description
        "OFA Error - Out of memory";
    }
    leaf err-id-reserve {
      type uint32;
      description
        "OFA Error - Reserve ID";
    }
    leaf err-id-release {
      type uint32;
      description
        "OFA Error - Release ID";
    }
    leaf err-id-update {
      type uint32;
      description
        "OFA Error - Update ID";
    }
  }

  grouping OFA-NPD-SYSDB-TABLE-RESOURCE {
    description
      "Table resources";
    container tbl-resources-stats {
      description
        "Generic OFA infra counters";
      uses OFA-SYSDB-TABLE-RESOURCE;
    }
    list user-defined-stat {
      description
        "Platform specific user defined stats";
      uses OFA-USER-DEFINED-STATS;
    }
  }
}
